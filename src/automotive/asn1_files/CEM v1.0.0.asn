CEM-PDU-Descriptions {
itu-t (0) identified-organization (4) etsi (0) itsDomain (5) wg1 (1) en (999999) cem (2) version (1) 
}

DEFINITIONS AUTOMATIC TAGS ::=

BEGIN

-- Data types

-- Patched ItsPduHeader with CEM identifier
StationID ::= INTEGER(0..4294967295)

ItsPduHeader ::= SEQUENCE {
    protocolVersion INTEGER (0..255),
    messageID INTEGER{ denm(1), cam(2), poi(3), spatem(4), mapem(5), ivim(6), ev-rsr(7), tistpgtransaction(8), srem(9), ssem(10), evcsn(11), saem(12), rtcmem(13), cem(200) } (0..255),  -- Mantis #7209, #7005
    stationID StationID
}

-- 64 bits cemTimestamp
CemTimestamp ::= INTEGER {utcStartOf2004(0), oneNanosecAfterUTCStartOf2004(1)} (0..18446744073709551615)

-- IDs
FullPrecisionID ::= INTEGER (0..65535)
DifferentialID ::= INTEGER (0..8)

-- Signal satellite information
-- We can use here an enumerated
ConstellationID ::= ENUMERATED {unavailable(0), gps(1), gal(2), bds(3), glo(4)}

-- Values from 1 to 32
SatellitePRN ::= INTEGER (1..32)

-- Pseudorange (considering around 40 bits to represent up to 2.4*10^7*10^3 mm)
Pseudorange ::= INTEGER {oneMilliMeter(1),oneMeter(1000)} (1..24000000000)

-- Differential Pseudorange (which are the units here?)
DifferentialPseudorange ::= INTEGER (-64000..64000)

-- PseudorangeUncertainty (consider up to 20*100 (0.01 precision) = 20000 = around 15 bits - 12 do not seem enough) - same for Carrier-phase and Doppler uncertainty
GPSDataUncertainty ::= INTEGER (0..20000)

-- Carrier-phase (consider up to 1.2*10^8*10^5 (10^-5 precision) = it would need around 44 bits)
CarrierPhase ::= INTEGER(0..12000000000000)

-- Differential Carrier-phase (consider 24 bits = max quantity: 16777215)
DifferentialCarrierPhase ::= INTEGER(0..16777215)

-- Doppler (in mHz)
Doppler ::= INTEGER {oneMilliHertz(1), oneHertz(1000)} (-5000000..5000000)

-- Doppler (differential, in mHz, considering 20 bits signed)
DifferentialDoppler ::= INTEGER(-524288..524287)

-- Signal Strenght (range: 20 dB-Hz to 70 dB-Hz)
SignalStrenght ::= INTEGER(20..70)

--	The root data frame for CEM messages
CEM ::= SEQUENCE {
	header ItsPduHeader,
	cem CoopEnhancement
}

CoopEnhancement ::= CHOICE {
	fps FullPrecisionInterframe,
	dmf DifferentialMicroframe,
	...
}

FullPrecisionInterframe ::= SEQUENCE {
	fullPrecisionID FullPrecisionID,
	cemTstamp CemTimestamp,
	satelliteSignalInfo SEQUENCE (SIZE (1..8)) OF SatelliteSignalInfo
}

SatelliteSignalInfo ::= SEQUENCE {
	mandatoryContainer MandatoryContainer,
	optionalContainer OptionalContainer OPTIONAL
}

MandatoryContainer ::= SEQUENCE {
	constellationID ConstellationID,
	satellitePRN SatellitePRN,
	pseudorange Pseudorange,
	pseudorangeUncertainty GPSDataUncertainty
}

OptionalContainer ::= SEQUENCE {
	carrierPhase CarrierPhase,
	carrierPhaseUncertainty GPSDataUncertainty,
	doppler Doppler,
	dopplerUncertainty GPSDataUncertainty
}

DifferentialMicroframe ::= SEQUENCE {
	fullPrecisionID FullPrecisionID,
	differentialID DifferentialID,
	cemTstamp CemTimestamp,
	differentialSatelliteSignalInfo SEQUENCE (SIZE (1..8)) OF DifferentialSatelliteSignalInfo
}

DifferentialSatelliteSignalInfo ::= SEQUENCE {
	differentialMandatoryContainer DifferentialMandatoryContainer,
	differentialOptionalContainer DifferentialOptionalContainer OPTIONAL
}

DifferentialMandatoryContainer ::= SEQUENCE {
	constellationID ConstellationID,
	satellitePRN SatellitePRN,
	differentialPseudorange DifferentialPseudorange
}

DifferentialOptionalContainer ::= SEQUENCE {
	differentialCarrierPhase DifferentialCarrierPhase,
	differentialCarrierPhaseUncertainty GPSDataUncertainty,
	differentialDoppler DifferentialDoppler,
	differentialDopplerUncertainty GPSDataUncertainty
}

END
