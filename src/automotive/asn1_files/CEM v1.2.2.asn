-- CEM v1.2.2

CEM-PDU-Descriptions {
itu-t (0) identified-organization (4) etsi (0) itsDomain (5) wg1 (1) en (999999) cem (2) version (1) 
}

DEFINITIONS AUTOMATIC TAGS ::=

BEGIN

-- Data types

-- Patched ItsPduHeader with CEM identifier
StationID ::= INTEGER(0..4294967295)

ItsPduHeader ::= SEQUENCE {
    protocolVersion INTEGER (0..255),
    messageID INTEGER{ denm(1), cam(2), poi(3), spatem(4), mapem(5), ivim(6), ev-rsr(7), tistpgtransaction(8), srem(9), ssem(10), evcsn(11), saem(12), rtcmem(13), cem(200) } (0..255),  -- Mantis #7209, #7005
    stationID StationID
}

-- 64 bits cemTimestamp
CemTimestamp ::= INTEGER {utcStartOf2004(0), oneNanosecAfterUTCStartOf2004(1)} (0..9223372036854775807)

-- IDs
FullPrecisionID ::= INTEGER (0..65535)
DifferentialID ::= INTEGER (0..8)

-- Signal satellite information
-- Enumarate the combination of Constellation and Signal Band, some values are left empty for possible additions at a later time (SBAS, QZSS, IRNSS)
SignalID ::= INTEGER {unavailable(0), gpsL1(1), gpsL2(2), gpsL5(3), gloG1(6), gloG2(7), gloG3(8), galE1(11), galE2(12), galE5a(13), galE5b(14), galE6(15), beiB1(18), beiB2(19), beiB3(20)} (0..31)

-- Values from 1 to 32
SatellitePRN ::= INTEGER {unavailable(0)} (0..32)

-- Pseudorange (considering around 40 bits to represent up to 2.9*10^7*10^2 cm)
Pseudorange ::= INTEGER {oneCentiMeter(1),oneMeter(100),unavailable(2900000001)} (1800000000..2900000001)

-- Differential Pseudorange (+- 1000 meters with cm precision)
DifferentialPseudorange ::= INTEGER {oneCentimeter(1),oneMeter(100),unavailable(100001)} (-100000..100001)

-- PseudorangeUncertainty (consider up to 20*10 (0.1 precision) = 2000 = around 11 bits) 
GPSDataUncertainty ::= INTEGER {unavailable(201)} (0..201)

-- Carrier-phase (consider up to 1.6*10^8*10^5 (10^-3 precision) = it would need around 44 bits)
CarrierPhase ::= INTEGER {unavailable(160000000001)} (70000000000..160000000001)

-- Differential Carrier-phase (+- 5500 cycles with 10^-3 precision)
DifferentialCarrierPhase ::= INTEGER {unavailable(5500001)} (-5500000..5500001)

-- Doppler (in mHz)
Doppler ::= INTEGER {oneMilliHertz(1), oneHertz(1000), unavailable(5000001)} (-5000000..5000001)

-- Doppler (differential, in mHz, max value found is 16.6 Hz)
DifferentialDoppler ::= INTEGER {oneMilliHertz(1), oneHertz(1000), unavailable(30001)} (-30000..30001)

-- Signal Strength (range: 20 dB-Hz to 70 dB-Hz + 71 as 'unavailable')
SignalStrength ::= INTEGER {unavailable(201)} (0..201)

--	The root data frame for CEM messages
CEM ::= SEQUENCE {
	header ItsPduHeader,
	cem CoopEnhancement
}

CoopEnhancement ::= CHOICE {
	fps FullPrecisionInterframe,
	dmf DifferentialMicroframe,
	...
}

FullPrecisionInterframe ::= SEQUENCE {
	fullPrecisionID FullPrecisionID,
	cemTstamp CemTimestamp,
	satelliteSignalInfo SEQUENCE (SIZE (1..200)) OF SatelliteSignalInfo
}

SatelliteSignalInfo ::= SEQUENCE {
	mandatoryContainer MandatoryContainer,
	optionalContainer OptionalContainer OPTIONAL,
	uncertaintyContainer UncertaintyContainer OPTIONAL
}

MandatoryContainer ::= SEQUENCE {
	signalID SignalID,
	satellitePRN SatellitePRN,
	pseudorange Pseudorange
}

OptionalContainer ::= SEQUENCE {	
	carrierPhase CarrierPhase,	
	doppler Doppler,	
	signalStrength SignalStrength
}

UncertaintyContainer ::= SEQUENCE {
	pseudorangeUncertainty GPSDataUncertainty,
	carrierPhaseUncertainty GPSDataUncertainty,
	dopplerUncertainty GPSDataUncertainty
}

DifferentialMicroframe ::= SEQUENCE {
	fullPrecisionID FullPrecisionID,
	differentialID DifferentialID,
	cemTstamp CemTimestamp,
	differentialSatelliteSignalInfo SEQUENCE (SIZE (1..200)) OF DifferentialSatelliteSignalInfo
}

DifferentialSatelliteSignalInfo ::= SEQUENCE {
	differentialMandatoryContainer DifferentialMandatoryContainer,
	differentialOptionalContainer DifferentialOptionalContainer OPTIONAL
}

DifferentialMandatoryContainer ::= SEQUENCE {
	differentialPseudorange DifferentialPseudorange
}

DifferentialOptionalContainer ::= SEQUENCE {
	differentialCarrierPhase DifferentialCarrierPhase,
	differentialDoppler DifferentialDoppler
}

END
